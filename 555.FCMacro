import FreeCAD as App
import Draft 
import numpy as np
import pandas as pd
import math as m
from numpy import genfromtxt
import numpy as np

def make_grid(grid_direction, dx, dy, initial_point_x, initial_point_y, piles_offset_dx, piles_offset_dy, n_piles_x, n_piles_y):
    if grid_direction == "north-west":
        direction_coeff_x = 1
        direction_coeff_y = -1

    elif grid_direction == "north-east":
        direction_coeff_x = 1
        direction_coeff_y = 1

    elif grid_direction == "south-west":
        direction_coeff_x = -1
        direction_coeff_y = -1

    elif grid_direction == "south-east":
        direction_coeff_x = -1
        direction_coeff_y = 1
    else:
        raise ValueError("Invalid grid_direction value")

    x = np.linspace(initial_point_x, initial_point_x + dx * (n_piles_x - 1) * direction_coeff_x, n_piles_x)
    y = np.linspace(initial_point_y, initial_point_y + dy * (n_piles_y - 1) * direction_coeff_y, n_piles_y)

    xv, yv = np.meshgrid(x, y)
    array = np.zeros((n_piles_x * n_piles_y, 2)) 
    k = 0

    for i in range(xv.shape[1]):
        for j in range(xv.shape[0]):
            X = xv[i, j]
            Y = yv[i, j]
            array[k, 0] = X
            array[k, 1] = Y
            k +=1
        
    return array

def arrow_func(x, y, dx, dy, scale, pile_size, text_size):
    # определение условного знака сваи
    pl = FreeCAD.Placement()
    pl.Base = FreeCAD.Vector(0, 0)
    circle_icon = Draft.make_circle(radius=5 * pile_size, placement=pl, face=False, support=None)
    pl2 = FreeCAD.Placement()
    pl2.Base = FreeCAD.Vector(-5 * pile_size, -5 * pile_size)
    rectangle_icon = Draft.make_rectangle(10 * pile_size, 10 * pile_size, placement=pl2, face=False, support=None)
    Obliq1 = Draft.makeLine(App.Vector(-5 * pile_size, 5 * pile_size), App.Vector(5 * pile_size, -5 * pile_size))
    Obliq2 = Draft.makeLine(App.Vector(5 * pile_size, 5 * pile_size), App.Vector(-5 * pile_size, -5 * pile_size))    
    # определение стрелок
    arrow_element1 = Draft.makeLine(App.Vector(0, 0), App.Vector(8 * pile_size, 0))
    arrow_element2 = Draft.makeLine(App.Vector(8 * pile_size, 0), App.Vector(6 * pile_size, 1 * pile_size))
    arrow_element3 = Draft.makeLine(App.Vector(8 * pile_size, 0), App.Vector(6 * pile_size, -1 * pile_size))    
    arrow2_element1 = Draft.makeLine(App.Vector(0, 0), App.Vector(8 * pile_size, 0))
    arrow2_element2 = Draft.makeLine(App.Vector(8 * pile_size, 0), App.Vector(6 * pile_size, 1 * pile_size))
    arrow2_element3 = Draft.makeLine(App.Vector(8 * pile_size, 0), App.Vector(6 * pile_size, -1 * pile_size))
    FreeCAD.ActiveDocument.recompute()
    # определение подписи отклонений
    p1 = App.Vector(9 * pile_size, -1 * pile_size)
    deviation_label_N_S = Draft.make_text(str(abs(dx)), p1)
    deviation_label_N_S.ViewObject.FontSize = 0.0030 * text_size      
    deviation_label_E_W = Draft.make_text(str(abs(dy)), p1)
    deviation_label_E_W.ViewObject.FontSize = 0.0030 * text_size
    FreeCAD.ActiveDocument.recompute()
    # группировка объектов
    icon_group = App.ActiveDocument.addObject("App::DocumentObjectGroup", 'icon_group')
    icon_group.addObjects([circle_icon, rectangle_icon, Obliq1, Obliq2]) # группа условного знака сваи
    arrow_group1 = App.ActiveDocument.addObject("App::DocumentObjectGroup", 'arrow_group1')
    arrow_group1.addObjects([arrow_element1, arrow_element2, arrow_element3, deviation_label_N_S]) # группировка стрелки направления север-юг с подписью
    arrow_group2 = App.ActiveDocument.addObject("App::DocumentObjectGroup", 'arrow_group2')
    arrow_group2.addObjects([arrow2_element1, arrow2_element2, arrow2_element3, deviation_label_E_W]) # группировка стрелки направления запад-восток с подписью
    App.ActiveDocument.recompute()
    # Повороты стрелок в зависимости от направления отклонения
    if dx > 0: 
        Draft.rotate(arrow_group1.OutList, 90, pl.Base)
    elif dx < 0: 
        Draft.rotate(arrow_group1.OutList, 270, pl.Base)
    elif dx == 0:
        Draft.rotate(arrow_group1.OutList, 0, pl.Base)
    if dy > 0:
        Draft.rotate(arrow_group2.OutList, 360, pl.Base)
        FreeCAD.ActiveDocument.recompute()
    elif dy < 0:
        Draft.rotate(arrow_group2.OutList, -180, pl.Base)
        Draft.rotate(deviation_label_E_W, 180, center=App.Vector(-10.5 * pile_size, 0.0, 0))
    elif dy == 0:
        Draft.rotate(arrow_group2.OutList, 90, pl.Base)
    App.ActiveDocument.recompute()
    # перемещение экземпляра сваи в точку с задаными координатами x,y
    Draft.move(icon_group.OutList, FreeCAD.Vector(x, y), copy=False)
    Draft.move(arrow_group2.OutList, FreeCAD.Vector(x, y), copy=False)
    Draft.move(arrow_group1.OutList, FreeCAD.Vector(x, y), copy=False)
    App.ActiveDocument.recompute()

    # масштабирование экземпляра сваи
    scale_vector = App.Vector(scale, scale)
    center_of_scaling = App.Vector(x, y)
    Draft.scale(icon_group.OutList, scale=scale_vector, center=center_of_scaling, copy=False)
    Draft.scale(arrow_group2.OutList, scale=scale_vector, center=center_of_scaling, copy=False)
    Draft.scale(arrow_group1.OutList, scale=scale_vector, center=center_of_scaling, copy=False)
    circle_icon.Radius = circle_icon.Radius * scale
    FreeCAD.ActiveDocument.recompute()


def outlers(grid, arr):
    outlers_arr = np.zeros((grid.shape[0], 2))
    for i in range(grid.shape[0]):
        dev_x = arr[:, 0] - grid[i, 0]
        dev_y = arr[:, 1] - grid[i, 1]
        dev_xy = dev_x ** 2 + dev_y ** 2 
        index_min = np.argmin(dev_xy)
        outlers_arr[i, 0] = dev_x[index_min]
        outlers_arr[i, 1] = dev_y[index_min]
    return outlers_arr

# масштаб
pile_size = 5
text_size = 3
# начальная точка
initial_point_x = 10
initial_point_y = 10
# Шаг
dx = 5
dy = 5
# Количество свай по оси Х и Y
n_piles_x = 5
n_piles_y = 5
# направление
grid_direction = "north-east"
piles_offset_dx = 0
piles_offset_dy = 0
# делаем сетку по ДС
grid = make_grid(grid_direction, dx, dy, initial_point_x, initial_point_y, piles_offset_dx, piles_offset_dy, n_piles_x, n_piles_y)
# импортируем файл с "модельными измерениями"
arr = np.genfromtxt("C:/Users/julia/OneDrive/Рабочий стол/qq.csv", delimiter=";", dtype=None, encoding='utf8')
# вычисляем отклонения
deviations = outlers(grid, arr)
deviations = np.round(deviations, 1) * 1000
grid2 = grid * pile_size
for i in range(grid.shape[0]):
    arrow_func(grid2[i, 0], grid2[i, 1], deviations[i, 0], deviations[i, 1], 0.2, pile_size, text_size)
