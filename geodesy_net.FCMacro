import os
import re
import pandas as pd
import numpy as np
import math
from scipy.spatial import Delaunay, KDTree
import FreeCAD, FreeCADGui
import Draft
import shutil
import Part
from PySide2.QtWidgets import QDialog, QVBoxLayout, QFormLayout, QLineEdit, QComboBox, QSpinBox, QCheckBox, QPushButton, QFileDialog, QTextEdit
from PySide2.QtGui import QFont


class MyWindow(QDialog):
    def __init__(self):
        super().__init__()

        self.points_amount = None  # кол-во пунктов
        self.gen_method = None     # метод генерации
        self.gen_radius = None     # Радиус генерации (относительно стартового пункта)
        self.min_distance = None   # Минимальное расстояние между пунктами
        self.max_distance = None   # Максимальное расстояние между пунктами
        self.reference_coords_X = None
        self.reference_coords_Y = None

        self.temp_file_name = ''  # Переменные для хранения имен временных файлов
		
        folder_name = 'Data'  # Папка для временных файлов и сохранения
       	
        if not os.path.exists(folder_name):  # Проверяем наличие папки Data
            os.makedirs(folder_name)
        else:
            self.script_dir = os.path.dirname(os.path.abspath(__file__))  # Определяем расположение директории
            self.data_dir = os.path.join(self.script_dir, 'Data')         # Определяем расположения папки для файлов

        self.createUI()


    def createUI(self):
        layout = QVBoxLayout()

        form_layout = QFormLayout()

        self.points_spinbox = QSpinBox()
        self.points_spinbox.setRange(3, 100)
        self.points_spinbox.setSingleStep(1)
        self.points_spinbox.setValue(10)
        self.method_input = QComboBox()
        self.method_input.addItems(['centralized', 'consistent', 'radial'])
        self.gen_radius_input = QLineEdit()
        self.gen_radius_input.setText('1000000')

        self.reference_coords_X_textbox = QLineEdit()
        self.reference_coords_X_textbox.setText('10')
        self.reference_coords_Y_textbox = QLineEdit()
        self.reference_coords_Y_textbox.setText('10')

        self.min_distance_input = QLineEdit()
        self.min_distance_input.setText('10000')
        self.max_distance_input = QLineEdit()
        self.max_distance_input.setText('20000')

        form_layout.addRow('Num of points:', self.points_spinbox)
        form_layout.addRow('Generation method:', self.method_input)
        form_layout.addRow('Gen radius (deg):', self.gen_radius_input)
        form_layout.addRow('Min distance (m):', self.min_distance_input)
        form_layout.addRow('Max distance (m):', self.max_distance_input)
        form_layout.addRow('Reference coordinate X:', self.reference_coords_X_textbox)
        form_layout.addRow('Reference coordinate Y:', self.reference_coords_Y_textbox)

        layout.addLayout(form_layout)

        self.create_button = QPushButton('Create')
        self.create_button.clicked.connect(self.btn1_press)
        layout.addWidget(self.create_button)

        self.show_network_button = QPushButton('Show network map')
        self.show_network_button.clicked.connect(self.btn2_press)
        layout.addWidget(self.show_network_button)

        self.save_button = QPushButton('Save to file')
        self.save_button.clicked.connect(self.btn3_press)
        layout.addWidget(self.save_button)

        self.load_csv_button = QPushButton('Load CSV')
        self.load_csv_button.clicked.connect(self.load_csv_file)
        layout.addWidget(self.load_csv_button)

        self.command_line = QTextEdit(self)
        self.command_line.setStyleSheet("background-color: black; color: white;")
        self.command_line.setFont(QFont("Courier", 10))
        layout.addWidget(self.command_line)

        self.setLayout(layout)
        self.setWindowTitle('Synthetic TimeSeries data app')
    

    def load_csv_file(self):
        options = QFileDialog.Options()
        file_name, _ = QFileDialog.getOpenFileName(self, "Load CSV Data File", "", "CSV Files (*.csv)", options=options)
        if file_name:
            self.temp_file_xyz_name = file_name
            self.command_line.append(f"CSV Data File loaded: {self.temp_file_xyz_name}")

    def btn1_press(self):
        self.command_line.append('Creating model...')
        
        self.points_amount = self.points_spinbox.value()
        self.gen_method = self.method_input.currentText()
        self.gen_radius = float(self.gen_radius_input.text())
        self.min_distance = int(self.min_distance_input.text())
        self.max_distance = int(self.max_distance_input.text())
        self.reference_coords_X = float(self.reference_coords_X_textbox.text())
        self.reference_coords_Y = float(self.reference_coords_Y_textbox.text())

        points = self.create_random_points(self.gen_method)
        self.generate_time_series(points)

        self.command_line.append("Model created")


    def create_random_points(self, method):
	
        if self.min_distance > self.max_distance:
            raise ValueError("Minimum distance cannot be greater than maximum distance")

        
        start_point = (self.reference_coords_X , self.reference_coords_Y)
        points = [start_point]
	        
        while len(points) < self.points_amount:
	        # Generate a random direction (angle in radians)
            direction = np.random.uniform(0, 2 * math.pi)

            # Generate a random distance within the specified range
            distance = np.random.uniform(self.min_distance, self.max_distance)

            # Calculate the new point's coordinates
            prev_x, prev_y = points[-1]
            x = prev_x + distance * math.cos(direction)
            y = prev_y + distance * math.sin(direction)

            point = (x, y)
            '''
            x = np.random.uniform(self.reference_coords_X - self.gen_radius, self.reference_coords_X + self.gen_radius)
            y = np.random.uniform(self.reference_coords_Y - self.gen_radius, self.reference_coords_Y + self.gen_radius)
            point = (x, y)
            '''
	        # Build a KD tree from the Cartesian coordinates
            tree = KDTree(points)

            if len(points) < 2:
                neighbours = 1
            else:
                neighbours = 2

            # Find the nearest point to the new point
            dist, idx = tree.query((x, y), k=neighbours)
 
            #geod_dist = self.calculate_distance()

            # Check if the distance is within the desired range
            if np.all(self.min_distance <= dist) and np.all(dist <= self.max_distance):
                # Add new point to list
                points.append(point)
                '''
                if method == 'consistent':
                    start_point = point
                elif method == 'centralized':
                    pass
                '''
        return points

        '''
        if method == 'radial':
            points = []
            points.append((self.reference_coords_X , self.reference_coords_Y ))

            for i in range(1, self.points_amount):
                # Generate a random direction (angle in radians)
                direction = np.random.uniform(0, 2 * math.pi)

                # Generate a random distance within the specified range
                distance = np.random.uniform(self.min_distance, self.max_distance)

                # Calculate the new point's coordinates
                prev_x, prev_y = points[-1]
                new_x = prev_x + distance * math.cos(direction)
                new_y = prev_y + distance * math.sin(direction)

                points.append((new_x, new_y))

            return points
         '''

    def generate_time_series(self, points):
        data = []

        for i, point in enumerate(points):
            X, Y = point
            station_name = ''.join(np.random.choice(list('ABCDEFGHIJKLMNOPQRSTUVWXYZ'), 4))

            height = np.random.uniform(0, 100)

            data.append({'Station': station_name,
                         'X': X,
                         'Y': Y,
                         'Height': height})

        df = pd.DataFrame(data)
        self.temp_file_name = os.path.join(self.data_dir, 'temp.csv')
        df.to_csv(self.temp_file_name, sep=';', index=False)

        self.command_line.append(f"Time series generated and saved to file: {self.temp_file_name}")


    def btn2_press(self):
        try:
            if not self.temp_file_name:
                self.command_line.append("No CSV file loaded. Please load a CSV file first.")
                return

            doc = FreeCAD.newDocument("NetworkMap")
            data = pd.read_csv(self.temp_file_name, delimiter=';')

            points = np.array(data[['X', 'Y']])
            labels = data['Station'].astype(str).values
            
            max_vector_length = self.max_distance  # adjust this value to set the maximum vector length

            tri = Delaunay(points)
            edges = set()
            # получаем все ребра треугольников и добавляем их в множество edges
            for n in range(tri.nsimplex):
                simplex = tri.simplices[n]
                for i in range(3):
                    for j in range(i, 3):
                        if i != j:
                            edges.add((simplex[i], simplex[j]))

            # рисуем ребра треугольников на графике и добавляем текст с длиной линий
            edge_labels = set()
            for edge in edges:
                x1, y1 = data.iloc[edge[0]][['X', 'Y']]
                x2, y2 = data.iloc[edge[1]][['X', 'Y']]
                length = self.calculate_distance(x1, y1, x2, y2)
                if length <= max_vector_length:  # проверяем длину линии
                    label = f'{length:.0f} m'
                    edge_labels.add((min(edge), max(edge), label))
                    point_1 = FreeCAD.Vector(x1, y1, 0)
                    point_2 = FreeCAD.Vector(x2, y2, 0)
                    line = Draft.makeLine(point_1, point_2)
                    doc.recompute()
            
            # рисуем текст с информацией о длинах линий
            for label in edge_labels:
                edge = label[:2]
                label_text = label[2]
                x1, y1 = data.iloc[edge[0]][['X', 'Y']]
                x2, y2 = data.iloc[edge[1]][['X', 'Y']]
                label_x = (x1 + x2) / 2
                label_y = (y1 + y2) / 2
                rotation = np.rad2deg(np.arctan2(y2 - y1, x2 - x1))
                if rotation > 90:
                    rotation -= 180
                elif rotation < -90:
                    rotation += 180
                
                midpoint = ((x1 + x2) / 2, (y1 + y2) / 2)
                text_obj = Draft.make_text(label_text, FreeCAD.Vector(*midpoint))
                text_obj.Placement = FreeCAD.Placement(FreeCAD.Vector(*midpoint), FreeCAD.Rotation(rotation, 0, 0))
                if text_obj is not None:
                    text_obj.ViewObject.FontSize = 1000

            # рисуем текст названий пунктов
            for i, point in enumerate(points):
                label = labels[i]
                
                offset = FreeCAD.Vector(0.01, 0.01, 0)
                text_position = FreeCAD.Vector(point[0], point[1], 0) + offset
                text = Draft.make_text([label], text_position)
         
                if text is not None:
                    text.ViewObject.FontSize = 1500  # Размер шрифта названий пунктов

            FreeCADGui.activeDocument().activeView().viewAxometric()
            FreeCADGui.SendMsgToActiveView("ViewFit")
        except Exception as e:
            self.command_line.append(f'Error generating network map: {e}')


    def btn3_press(self):
        try:
            save_path, _ = QFileDialog.getSaveFileName(self, "Save File", "", "CSV Files (*.csv)")
            if save_path:
                shutil.copyfile(self.temp_file_xyz_name, save_path)
                self.command_line.append("File saved.")
        except Exception as e:
            self.command_line.append(f'Error saving file: {e}')


    def calculate_distance(self, x1, y1, x2, y2):
        return math.sqrt((x2 - x1)**2 + (y2 - y1)**2)


if __name__ == '__main__':
    main_window = MyWindow()
    main_window.exec_()
